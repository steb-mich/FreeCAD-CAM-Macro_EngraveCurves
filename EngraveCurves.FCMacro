import FreeCAD as App
import FreeCADGui as Gui
import Part
import math
import Path
from PySide import QtWidgets, QtCore, QtGui

doc = App.ActiveDocument

# -----------------------------
# TASK PANEL
# -----------------------------
class EngraveTaskPanel:
    def __init__(self):
        self.collected_edges = []
        self.form = QtWidgets.QWidget()
        self.form.setWindowTitle("Engrave Curves Operation")
        main_layout = QtWidgets.QVBoxLayout(self.form)

        # --- JOB SELECTION ---
        job_group = QtWidgets.QGroupBox("Job")
        job_layout = QtWidgets.QFormLayout()
        self.job_combo = QtWidgets.QComboBox()
        self.jobs = [o for o in doc.Objects if hasattr(o, "Operations")]
        for j in self.jobs:
            self.job_combo.addItem(j.Label)
        job_layout.addRow("Job:", self.job_combo)
        job_group.setLayout(job_layout)
        main_layout.addWidget(job_group)

        # --- TOOL SELECTION ---
        tool_group = QtWidgets.QGroupBox("Tool Controller")
        tool_layout = QtWidgets.QFormLayout()
        self.tool_combo = QtWidgets.QComboBox()
        self.job_combo.currentIndexChanged.connect(self.populate_tools)
        tool_layout.addRow("Tool:", self.tool_combo)
        tool_group.setLayout(tool_layout)
        main_layout.addWidget(tool_group)

        # --- EDGES LIST ---
        edges_group = QtWidgets.QGroupBox("Edges / Curves")
        edges_layout = QtWidgets.QVBoxLayout()

        self.edge_list = QtWidgets.QTableWidget(0, 3)
        self.edge_list.setHorizontalHeaderLabels(["Edge / Curve", "Reverse", "Link"])
        self.edge_list.horizontalHeader().setSectionResizeMode(0, QtWidgets.QHeaderView.Stretch)
        self.edge_list.horizontalHeader().setSectionResizeMode(1, QtWidgets.QHeaderView.ResizeToContents)
        self.edge_list.horizontalHeader().setSectionResizeMode(2, QtWidgets.QHeaderView.ResizeToContents)
        self.edge_list.setSelectionBehavior(QtWidgets.QAbstractItemView.SelectRows)
        self.edge_list.setSelectionMode(QtWidgets.QAbstractItemView.SingleSelection)
        self.edge_list.setEditTriggers(QtWidgets.QAbstractItemView.NoEditTriggers)
        edges_layout.addWidget(self.edge_list)

        btn_row = QtWidgets.QHBoxLayout()

        self.select_btn = QtWidgets.QPushButton("Select Edges")
        self.select_btn.setCheckable(True)
        self.select_btn.toggled.connect(self.toggle_select_mode)
        btn_row.addWidget(self.select_btn)

        self.add_btn = QtWidgets.QPushButton("Add Selected")
        self.add_btn.setEnabled(False)
        self.add_btn.clicked.connect(self.add_selected_edges)
        btn_row.addWidget(self.add_btn)

        self.del_btn = QtWidgets.QPushButton("Delete")
        self.del_btn.clicked.connect(self.delete_edge)
        btn_row.addWidget(self.del_btn)

        edges_layout.addLayout(btn_row)

        reorder_row = QtWidgets.QHBoxLayout()
        self.up_btn = QtWidgets.QPushButton("▲ Move Up")
        self.up_btn.clicked.connect(self.move_up)
        reorder_row.addWidget(self.up_btn)

        self.down_btn = QtWidgets.QPushButton("▼ Move Down")
        self.down_btn.clicked.connect(self.move_down)
        reorder_row.addWidget(self.down_btn)

        edges_layout.addLayout(reorder_row)
        edges_group.setLayout(edges_layout)
        main_layout.addWidget(edges_group)

        # --- PARAMETERS ---
        param_group = QtWidgets.QGroupBox("Parameters")
        param_layout = QtWidgets.QFormLayout()

        self.total_depth = QtWidgets.QDoubleSpinBox()
        self.total_depth.setRange(0.01, 100.0)
        self.total_depth.setDecimals(2)
        self.total_depth.setSuffix(" mm")
        self.total_depth.setValue(1.7)
        param_layout.addRow("Total Depth:", self.total_depth)

        self.step_down = QtWidgets.QDoubleSpinBox()
        self.step_down.setRange(0.01, 100.0)
        self.step_down.setDecimals(2)
        self.step_down.setSuffix(" mm")
        self.step_down.setValue(0.1)
        param_layout.addRow("Step Down:", self.step_down)

        self.safe_height = QtWidgets.QDoubleSpinBox()
        self.safe_height.setRange(0.1, 100.0)
        self.safe_height.setDecimals(2)
        self.safe_height.setSuffix(" mm")
        self.safe_height.setValue(5.0)
        param_layout.addRow("Safe Height:", self.safe_height)

        self.feed = QtWidgets.QDoubleSpinBox()
        self.feed.setRange(1, 10000)
        self.feed.setDecimals(0)
        self.feed.setSuffix(" mm/min")
        self.feed.setValue(800)
        param_layout.addRow("Feed Rate:", self.feed)

        self.plunge = QtWidgets.QDoubleSpinBox()
        self.plunge.setRange(1, 10000)
        self.plunge.setDecimals(0)
        self.plunge.setSuffix(" mm/min")
        self.plunge.setValue(200)
        param_layout.addRow("Plunge Rate:", self.plunge)

        self.step_res = QtWidgets.QDoubleSpinBox()
        self.step_res.setRange(0.001, 10.0)
        self.step_res.setDecimals(3)
        self.step_res.setSuffix(" mm")
        self.step_res.setValue(0.1)
        param_layout.addRow("Curve Resolution:", self.step_res)

        param_group.setLayout(param_layout)
        main_layout.addWidget(param_group)

        # populate tools for initially selected job
        self.populate_tools()

    def populate_tools(self):
        self.tool_combo.clear()
        idx = self.job_combo.currentIndex()
        if idx < 0 or idx >= len(self.jobs):
            return
        self.tools = []
        for obj in doc.Objects:
            if (obj.Name.startswith("TC_") or obj.Name.startswith("TC__") or
                    hasattr(obj, "ToolNumber")):
                self.tools.append(obj)
                self.tool_combo.addItem(obj.Label)

    def toggle_select_mode(self, checked):
        self.add_btn.setEnabled(checked)
        if checked:
            self.select_btn.setText("✋ Click edges in 3D view, then Add")
            Gui.Selection.clearSelection()
        else:
            self.select_btn.setText("Select Edges")

    def add_selected_edges(self):
        sel = Gui.Selection.getSelectionEx()
        added = 0
        for s in sel:
            for i, sub in enumerate(s.SubObjects):
                if isinstance(sub, Part.Edge):
                    subname = s.SubElementNames[i]
                    label = f"{s.Object.Label} → {subname}"
                    existing = [self.edge_list.item(r, 0).text()
                                for r in range(self.edge_list.rowCount())]
                    if label not in existing:
                        row = self.edge_list.rowCount()
                        self.edge_list.insertRow(row)
                        self.edge_list.setItem(row, 0, QtWidgets.QTableWidgetItem(label))

                        chk_rev = QtWidgets.QTableWidgetItem()
                        chk_rev.setFlags(QtCore.Qt.ItemIsUserCheckable | QtCore.Qt.ItemIsEnabled)
                        chk_rev.setCheckState(QtCore.Qt.Unchecked)
                        self.edge_list.setItem(row, 1, chk_rev)

                        chk_link = QtWidgets.QTableWidgetItem()
                        if row == 0:
                            chk_link.setFlags(QtCore.Qt.NoItemFlags)  # disabled for first row
                        else:
                            chk_link.setFlags(QtCore.Qt.ItemIsUserCheckable | QtCore.Qt.ItemIsEnabled)
                        chk_link.setCheckState(QtCore.Qt.Unchecked)
                        self.edge_list.setItem(row, 2, chk_link)

                        self.collected_edges.append((s.Object, subname, sub))
                        added += 1
        Gui.Selection.clearSelection()
        if added == 0:
            QtWidgets.QMessageBox.warning(
                self.form, "No edges",
                "No edges found in current selection.\n"
                "Please click edges in the 3D view first.")
	
    def _fix_link_flags(self):
        """Row 0 can never be linked; all other rows can be."""
        for row in range(self.edge_list.rowCount()):
            item = self.edge_list.item(row, 2)
            if row == 0:
                item.setFlags(QtCore.Qt.NoItemFlags)
                item.setCheckState(QtCore.Qt.Unchecked)
            else:
                item.setFlags(QtCore.Qt.ItemIsUserCheckable | QtCore.Qt.ItemIsEnabled)
	
    def delete_edge(self):
        row = self.edge_list.currentRow()
        if row >= 0:
            self.edge_list.removeRow(row)
            self.collected_edges.pop(row)

    def move_up(self):
        row = self.edge_list.currentRow()
        if row > 0:
            label_a = self.edge_list.item(row - 1, 0).text()
            label_b = self.edge_list.item(row,     0).text()
            chk_a   = self.edge_list.item(row - 1, 1).checkState()
            chk_b   = self.edge_list.item(row,     1).checkState()
            lnk_a   = self.edge_list.item(row - 1, 2).checkState()
            lnk_b   = self.edge_list.item(row,     2).checkState()
            self.edge_list.item(row - 1, 0).setText(label_b)
            self.edge_list.item(row,     0).setText(label_a)
            self.edge_list.item(row - 1, 1).setCheckState(chk_b)
            self.edge_list.item(row,     1).setCheckState(chk_a)
            self.edge_list.item(row - 1, 2).setCheckState(lnk_b)
            self.edge_list.item(row,     2).setCheckState(lnk_a)
            self.edge_list.setCurrentCell(row - 1, 0)
            self.collected_edges.insert(row - 1, self.collected_edges.pop(row))
            self._fix_link_flags()

    def move_down(self):
        row = self.edge_list.currentRow()
        if row >= 0 and row < self.edge_list.rowCount() - 1:
            label_a = self.edge_list.item(row,     0).text()
            label_b = self.edge_list.item(row + 1, 0).text()
            chk_a   = self.edge_list.item(row,     1).checkState()
            chk_b   = self.edge_list.item(row + 1, 1).checkState()
            lnk_a   = self.edge_list.item(row,     2).checkState()
            lnk_b   = self.edge_list.item(row + 1, 2).checkState()
            self.edge_list.item(row,     0).setText(label_b)
            self.edge_list.item(row + 1, 0).setText(label_a)
            self.edge_list.item(row,     1).setCheckState(chk_b)
            self.edge_list.item(row + 1, 1).setCheckState(chk_a)
            self.edge_list.item(row,     2).setCheckState(lnk_a)
            self.edge_list.item(row + 1, 2).setCheckState(lnk_b)
            self.edge_list.setCurrentCell(row + 1, 0)
            self.collected_edges.insert(row + 1, self.collected_edges.pop(row))
            self._fix_link_flags()

    def get_edges(self):
        result = []
        for i, (_, _, e) in enumerate(self.collected_edges):
            rev  = self.edge_list.item(i, 1).checkState() == QtCore.Qt.Checked
            link = self.edge_list.item(i, 2).checkState() == QtCore.Qt.Checked
            result.append((e, rev, link))
        return result

    # --- Called by FreeCAD when user clicks OK in task panel ---
    def accept(self):
        if not self.jobs:
            QtWidgets.QMessageBox.warning(self.form, "Error", "No Job found in document.")
            return
        if not hasattr(self, 'tools') or not self.tools:
            QtWidgets.QMessageBox.warning(self.form, "Error", "No Tool Controller found.")
            return
        if len(self.collected_edges) == 0:
            QtWidgets.QMessageBox.warning(self.form, "Error",
                "No edges selected. Please add at least one edge.")
            return

        job  = self.jobs[self.job_combo.currentIndex()]
        tool = self.tools[self.tool_combo.currentIndex()]
        edge_pairs = self.get_edges()

        TOTAL_DEPTH = self.total_depth.value()
        STEP_DOWN   = self.step_down.value()
        SAFE_HEIGHT = self.safe_height.value()
        FEED        = int(self.feed.value())
        PLUNGE      = int(self.plunge.value())
        STEP_RES    = self.step_res.value()

        # --- SAMPLE CURVES ---
        points = []

        def sample_edge(edge):
            length = edge.Length
            steps = max(2, int(length / STEP_RES))
            pts = []
            for i in range(steps + 1):
                d = (length / steps) * i
                d = min(d, length)
                param = edge.getParameterByLength(d)
                pts.append(edge.valueAt(param))
            return pts

        edge_point_lists = []
        for e, rev, link in edge_pairs:
            pts = sample_edge(e)
            if rev:
                pts = list(reversed(pts))
            edge_point_lists.append((pts, link))

        # --- SAFE HEIGHT ---
        all_points = [p for pts, _ in edge_point_lists for p in pts]
        max_z = max(p.z for p in all_points)
        safe_z = max_z + SAFE_HEIGHT

        # --- DEPTH CALCULATION ---
        passes = int(TOTAL_DEPTH // STEP_DOWN)
        remainder = TOTAL_DEPTH - passes * STEP_DOWN
        depths = [STEP_DOWN * (i+1) for i in range(passes)]
        if remainder > 0.001:
            depths.append(TOTAL_DEPTH)

        # --- BUILD GCODE ---
        gcode = f"G0 Z{safe_z:.3f}\n"
        for depth in depths:
            for idx, (pts, link) in enumerate(edge_point_lists):
                start = pts[0]
                if link and idx > 0:
                    # No retract — feed directly to start of this edge at current depth
                    gcode += f"G1 X{start.x:.3f} Y{start.y:.3f} Z{start.z - depth:.3f} F{FEED}\n"
                else:
                    gcode += f"G0 X{start.x:.3f} Y{start.y:.3f}\n"
                    gcode += f"G1 Z{start.z - depth:.3f} F{PLUNGE}\n"
                for p in pts[1:]:
                    gcode += f"G1 X{p.x:.3f} Y{p.y:.3f} Z{p.z - depth:.3f} F{FEED}\n"
                # Only retract if next edge is NOT linked to this one
                next_linked = (idx + 1 < len(edge_point_lists) and edge_point_lists[idx + 1][1])
                if not next_linked:
                    gcode += f"G0 Z{safe_z:.3f}\n"

        # --- CREATE PATH OBJECT ---
        import Path.Op.Custom as PathCustom
        import Path.Op.Gui.Base as PathOpGui
        import Path.Op.Gui.Custom as PathCustomGui

        # Close our task panel first before creating the op
        Gui.Control.closeDialog()

        # Use non-GUI Create to avoid triggering another task panel
        op = PathCustom.Create("Custom", parentJob=job)

        # Manually attach the ViewProvider
        res = PathOpGui.CommandResources(
            "Custom",
            PathCustom.Create,
            PathCustomGui.TaskPanelOpPage,
            "CAM_Custom",
            "Custom",
            None,
            "Custom GCode Operation"
        )
        if App.GuiUp:
            op.ViewObject.Proxy = PathOpGui.ViewProvider(op.ViewObject, res)
            op.ViewObject.Proxy.attach(op.ViewObject)

        op.ToolController = tool
        op.Source = "Text"
        op.Gcode = [line for line in gcode.split("\n") if line.strip()]

        doc.recompute()

        print("✅ Engrave path created successfully")

    # --- Called by FreeCAD when user clicks Cancel ---
    def reject(self):
        Gui.Control.closeDialog()
        print("❌ Engrave operation cancelled")


# -----------------------------
# LAUNCH TASK PANEL
# -----------------------------
panel = EngraveTaskPanel()
Gui.Control.showDialog(panel)
